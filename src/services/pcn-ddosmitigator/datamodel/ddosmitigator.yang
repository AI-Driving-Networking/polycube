module ddosmitigator {
  yang-version 1.1;
  namespace "http://polycube.network/ddosmitigator";
  prefix "ddosmitigator";

  import polycube-base { prefix "polycube-base"; }
  import polycube-transparent-base { prefix "polycube-transparent-base"; }

  organization "Polycube open source project";
  description "YANG data model for the Polycube DDoS Mitigator service";

  polycube-base:service-description "DDoS Mitigator Service";
  polycube-base:service-version "2.0";
  polycube-base:service-name "ddosmitigator";
  polycube-base:service-min-kernel-version "4.14.0";

  uses "polycube-transparent-base:transparent-base-yang-module";

  container stats {
    description "Statistics on dropped packets";
    config false;

    leaf pps {
      type uint64;
      config false;
      description "Dropped Packets/s";
    }

    leaf pkts {
      type uint64;
      config false;
      description "Total Dropped Packets";
    }
  }

  list blacklist-src {
      key "ip";
      description "Blacklisted source IP addresses";

      leaf ip {
        type string;
        description "Source IP Address";
        polycube-base:cli-example "10.0.0.1";
      }

      leaf drop-pkts {
        type uint64;
        config false;
        description "Dropped Packets";
      }
  }

  list blacklist-dst {
      key "ip";
      description "Blacklisted destination IP addresses";

      leaf ip {
        type string;
        description "Destination IP Address";
        polycube-base:cli-example "10.0.0.2";
      }

      leaf drop-pkts {
        type uint64;
        config false;
        description "Dropped Packets";
      }
  }

  container blacklist-src-file {
      description "Blacklist file";

      leaf file {
        type string;
        description "Absolute path of blacklist file";
        polycube-base:cli-example "/home/test/blacklist";
      }
  }

  leaf stats-mode {
      type enumeration {
          enum READ-ONLY;
          enum READ-CLEAR;
        }
      default "READ-ONLY";
      description "Stats mode, read stats only, or read the stats then clear it";
    }
}
